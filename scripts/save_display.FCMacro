from pathlib import Path
import json,traceback
import FreeCAD as App
import FreeCADGui as Gui
from PySide import QtCore
root=Path(__file__).resolve().parents[1]
try:
    Gui.getMainWindow().hide()
    doc=App.openDocument(str(root/'apex_racer.FCStd'))
    for o in doc.Objects:
        if 'DesignColor' in o.PropertiesList:
            o.ViewObject.ShapeColor=tuple(o.DesignColor[:3])
            if 'GlassFaces' in o.PropertiesList:
                colours=[tuple(o.DesignColor[:3]) for _ in o.Shape.Faces]
                for index in o.GlassFaces:colours[index]=(.075,.14,.18)
                for index in o.DetailFaces:colours[index]=(.16,.025,.035)
                if 'HeadlampBezelFaces' in o.PropertiesList:
                    for index in o.HeadlampBezelFaces:colours[index]=(.035,.055,.07)
                    for index in o.HeadlampLensFaces:colours[index]=(.72,.85,.92)
                o.ViewObject.DiffuseColor=colours
            o.ViewObject.LineColor=(.08,.09,.10)
            o.ViewObject.DisplayMode='Flat Lines'
            o.ViewObject.Visibility=True
    doc.recompute()
    Gui.activeDocument().activeView().viewAxonometric()
    Gui.activeDocument().activeView().fitAll()
    Gui.updateGui();doc.save()
    Gui.activeDocument().activeView().saveImage(str(root/'freecad_preview.png'),1500,1000,'White')
    (root/'display_report.json').write_text(json.dumps({'saved':True,'visible_parts':len(doc.Objects)}))
except Exception:(root/'display_error.txt').write_text(traceback.format_exc())
finally:QtCore.QTimer.singleShot(1000,Gui.getMainWindow().close)
